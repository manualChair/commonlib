;;;(include '*ISO-639-1* "./common/ISO-639-1")

;;; *ISO-639-1* : symbol (ISO-639-1 locale language name)

;;; +------------------------------------------------------+
;;;   Copyright (c) 2020 manual chair japan                 
;;;   Released under the MIT license                        
;;;   https://opensource.org/licenses/mit-license.php       
;;; +------------------------------------------------------+

(include 'default "./common/default")
(include 'typep "./types/typep")
(include 'assoc-if "./conses/assoc-if")

(setq *ISO-639-1:table*
       '((("AB" "ABK" "ABKS") . AB)
         (("AA" "AAR" "AARS") . AA)
         (("AF" "ABK" "AFRS") . AF)
         (("AK" "AKA") . AK)
         (("SQ" "SQI" "ALB") . SQ)
         (("AR" "ARA") . AR)
         (("AN" "ARG") . AN)
         (("HY" "HYE" "ARM") . HY)
         (("AS" "ASM") . AS)
         (("AV" "AVA") . AV)
         (("AE" "AVE") . AE)
         (("AY" "AYM") . AY)
         (("AZ" "AZE") . AZ)
         (("BA" "BAK") . BA)
         (("EU" "EUS" "BAQ") . EU)
         (("BE" "BEL") . BE)
         (("BN" "BEN") . BN)
         (("BH" "BIH") . BH)
         (("BI" "BIS") . BI)
         (("BS" "BOS" "BOSS") . BS)
         (("BR" "BRE") . BR)
         (("BG" "BUL" "BULS") . BG)
         (("MY" "MYA") . MY)
         (("CA" "CAT") . CA)
         (("CH" "CHA") . CH)
         (("CE" "CHE") . CE)
         (("NY" "NYA") . NY)
         (("ZH" "ZHO" "CHI") . ZH)
         (("CV" "CHV") . CV)
         (("KW" "COR") . KW)
         (("CO" "COS") . CO)
         (("CR" "CRE") . CR)
         (("HR" "HRV") . HR)
         (("CS" "CES" "CZE") . CS)
         (("DA" "DAN") . DA)
         (("DV" "DIV") . DV)
         (("NL" "NLD" "DUT") . NL)
         (("DZ" "DZO") . DZ)
         (("EN" "ENG" "ENGS") . EN)
         (("EO" "EPO") . EO)
         (("ET" "EST") . ET)
         (("EE" "EWE") . EE)
         (("FO" "FAO") . FO)
         (("FJ" "FIJ") . FJ)
         (("FI" "FIN") . FI)
         (("FR" "FRA" "FRE" "FRAS") . FR)
         (("FF" "FUL") . FF)
         (("GL" "GLG") . GL)
         (("KA" "KAT" "GEO") . KA)
         (("DE" "DEU" "GER" "DEUS") . DE)
         (("EL" "ELL" "GRE" "ELLS") . EL)
         (("GN" "GRN" "GRN") . GN)
         (("GU" "GUJ") . GU)
         (("HT" "HAT") . HT)
         (("HA" "HAU") . HA)
         (("HE" "HEB") . HE)
         (("HZ" "HER") . HZ)
         (("HI" "HIN" "HINS") . HI)
         (("HO" "HMO") . HO)
         (("HU" "HUN") . HU)
         (("IA" "INA") . IA)
         (("ID" "IND") . ID)
         (("IE" "ILE") . IE)
         (("GA" "GLE") . GA)
         (("IG" "IBO") . IG)
         (("IK" "IPK") . IK)
         (("IO" "IDO" "IDOS") . IO)
         (("IS" "ISL" "ICE") . IS)
         (("IT" "ITA" "ITAS") . IT)
         (("IU" "IKU") . IU)
         (("JA" "JPN") . JA)
         (("JV" "JAV") . JV)
         (("KL" "KAL") . KL)
         (("KN" "KAN") . KN)
         (("KR" "KAU") . KR)
         (("KS" "KAS") . KS)
         (("KK" "KAZ") . KK)
         (("KM" "KHM") . KM)
         (("KI" "KIK") . KI)
         (("RW" "KIN") . RW)
         (("KY" "KIR") . KY)
         (("KV" "KOM") . KV)
         (("KG" "KON") . KG)
         (("KO" "KOR") . KO)
         (("KU" "KUR") . KU)
         (("KJ" "KUA") . KJ)
         (("LA" "LAT" "LATS") . LA)
         (("LB" "LTZ") . LB)
         (("LG" "LUG") . LG)
         (("LI" "LIM") . LI)
         (("LN" "LIN") . LN)
         (("LO" "LAO") . LO)
         (("LT" "LIT") . LT)
         (("LU" "LUB") . LU)
         (("LV" "LAV") . LV)
         (("GV" "GLV") . GV)
         (("MK" "MKD" "MAC") . MK)
         (("MG" "MLG") . MG)
         (("MS" "MSA" "MAY") . MS)
         (("ML" "MAL") . ML)
         (("MT" "MLT") . MT)
         (("MI" "MRI" "MAO") . MI)
         (("MR" "MAR") . MR)
         (("MH" "MAH") . MH)
         (("MN" "MON") . MN)
         (("NA" "NAU") . NA)
         (("NV" "NAV") . NV)
         (("NB" "NOB") . NB)
         (("ND" "NDE") . ND)
         (("NE" "NEP") . NE)
         (("NG" "NDO") . NG)
         (("NN" "NNO") . NN)
         (("NO" "NOR") . NO)
         (("II" "III") . II)
         (("NR" "NBL") . NR)
         (("OC" "OCI") . OC)
         (("OJ" "OJI") . OJ)
         (("CU" "CHU") . CU)
         (("OM" "ORM") . OM)
         (("OR" "ORI") . OR)
         (("OS" "OSS") . OS)
         (("PA" "PAN") . PA)
         (("PI" "PLI") . PI)
         (("FA" "FAS" "PER") . FA)
         (("PL" "POL" "POLS") . PL)
         (("PS" "PUS") . PS)
         (("PT" "POR") . PT)
         (("QU" "QUE") . QU)
         (("RM" "ROH") . RM)
         (("RN" "RUN") . RN)
         (("RO" "RON" "RUM") . RO)
         (("RU" "RUS") . RU)
         (("SA" "SAN") . SA)
         (("SC" "SRD") . SC)
         (("SD" "SND") . SD)
         (("SE" "SME") . SE)
         (("SM" "SMO") . SM)
         (("SG" "SAG") . SG)
         (("SR" "SRP") . SR)
         (("GD" "GLA") . GD)
         (("SN" "SNA") . SN)
         (("SI" "SIN") . SI)
         (("SK" "SLK" "SLO") . SK)
         (("SL" "SLV") . SL)
         (("SO" "SOM") . SO)
         (("ST" "SOT") . ST)
         (("ES" "SPA") . ES)
         (("SU" "SUN") . SU)
         (("SW" "SWA") . SW)
         (("SS" "SSW") . SS)
         (("SV" "SWE") . SV)
         (("TA" "TAM") . TA)
         (("TE" "TEL") . TE)
         (("TG" "TGK") . TG)
         (("TH" "THA") . TH)
         (("TI" "TIR") . TI)
         (("BO" "BOD" "TIB") . BO)
         (("TK" "TUK") . TK)
         (("TL" "TGL") . TL)
         (("TN" "TSN") . TN)
         (("TO" "TON") . TO)
         (("TR" "TUR") . TR)
         (("TS" "TSO") . TS)
         (("TT" "TAT") . TT)
         (("TW" "TWI") . TW)
         (("TY" "TAH") . TY)
         (("UG" "UIG") . UG)
         (("UK" "UKR") . UK)
         (("UR" "URD") . UR)
         (("UZ" "UZB") . UZ)
         (("VE" "VEN") . VE)
         (("VI" "VIE") . VI)
         (("VO" "VOL") . VO)
         (("WA" "WLN") . WA)
         (("CY" "CYM" "WEL") . CY)
         (("WO" "WOL") . WO)
         (("FY" "FRY") . FY)
         (("XH" "XHO") . XH)
         (("YI" "YID") . YI)
         (("YO" "YOR") . YO)
         (("ZA" "ZHA") . ZA)
         (("ZU" "ZUL") . ZU)
        )
)

(defun ISO-639-1:search (locale / ISO-639-1:search:sub)
  (defun ISO-639-1:search:sub (locale)
    (cdr (assoc-if (function (lambda (key) (member locale key)))
                   *ISO-639-1:table*
         )
    )
  )
  ;;
  (setq locale (if (typep locale 'STR)
                 locale
                 (vl-symbol-name locale)
               )
  )
  (default (default (ISO-639-1:search:sub locale)
                    '(ISO-639-1:search:sub (subst locale 1 2))
           )
           'EN
  )
)


(setq *ISO-639-1* (ISO-639-1:search (getvar "LOCALE")))
